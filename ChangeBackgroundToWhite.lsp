(defun c:ChangeBackgroundToWhite ()
  "Изменяет цвет фона в модели на белый"
  ;; Установка цвета фона на белый (RGB: 255, 255, 255)
  (setvar "BACKGROUNDCOLOR" (rgb 255 255 255))
  ;; Обновление экрана для применения изменений
  (princ "\nЦвет фона успешно изменен на белый.")
  (princ)
)

;; Функция для преобразования RGB в значение цвета AutoCAD
(defun rgb (r g b)
  (cond ((and (<= 0 r 255) (<= 0 g 255) (<= 0 b 255))
         (+ (* r 65536) (* g 256) b))
        (t (progn 
             (princ "\nОшибка: Значения RGB должны быть в диапазоне от 0 до 255.")
             nil))))
