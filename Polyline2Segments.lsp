(defun c:Polyline2Segments ()
  ;; Запрос первой точки (начало полилинии)
  (setq pt1 (getpoint "\nУкажите первую точку (начало полилинии): "))
  
  ;; Запрос второй точки (конец полилинии)
  (setq pt2 (getpoint "\nУкажите вторую точку (конец полилинии): "))
  
  ;; Разбиваем координаты точек на X и Y
  (setq x1 (car pt1))
  (setq y1 (cadr pt1))
  (setq x2 (car pt2))
  (setq y2 (cadr pt2))
  
  ;; Определяем точку перегиба полилинии
  ;; Точка перегиба будет иметь координаты (x1, y2)
  (setq ptMid (list x1 y2)) ;; Точка перегиба
  
  ;; Создание полилинии
  (command "_.PLINE" pt1 ptMid pt2 "")
  
  ;; Сообщение об успешном завершении
  (princ "\nПолилиния успешно построена.")
  
  ;; Завершение программы
  (princ)
)
