(defun c:JoinToPolyline ( / ss)
  ;; Загрузка команды, если она еще не загружена
  (if (not (member "PEDIT" (list "PEDIT"))) (arxload "acad" nil))
  
  ;; Запрос выбора объектов у пользователя
  (prompt "\nВыберите линии/дуги/полилинии для объединения: ")
  (if (setq ss (ssget '((0 . "LINE,ARC,LWPOLYLINE"))))
    (progn
      ;; Вызов команды PEDIT в режиме "Multiple"
      (command "_.PEDIT" "_M" ss "" "_Y" "_J" "" "")
      
      ;; Опционально: попытка замкнуть полилинию
      ;; (если она уже является единой полилинией после объединения)
      (command "_.PEDIT" "_L" "_C" "")
      
      (princ "\nГотово. Создана единая полилиния.")
    )
    (princ "\nОбъекты не выбраны.")
  )
  (princ)
)

;; Альтернативный, более надежный вариант с использованием ActiveX
(defun c:JoinToPolyline2 ( / ss obj)
  (prompt "\nВыберите объекты для объединения: ")
  (if (setq ss (ssget '((0 . "LINE,ARC,LWPOLYLINE"))))
    (progn
      ;; Используем команду JOIN, которая в современных версиях работает стабильнее
      (command "_.JOIN" ss "")
      (princ "\nОбъекты объединены.")
    )
  )
  (princ)
)


;; LISP-код для AutoCAD, который преобразует выбранные линии (и дуги) в полилинии и объединяет все соприкасающиеся сегменты в единую полилинию (при возможности — замыкает её).
;; Первая команда (JoinToPolyline) использует классический PEDIT с опцией Multiple и Join. Это стандартный способ преобразования линий в полилинии и их объединения . Опция _C (Close) в конце пытается замкнуть получившуюся полилинию, если это возможно.
;; Вторая команда (JoinToPolyline2) использует более современную команду JOIN, которая появилась в AutoCAD 2012 и работает быстрее и стабильнее с большими наборами объектов.
;; Если линии имеют небольшие разрывы (не точно совпадают концы), PEDIT может их не соединить. В таких случаях можно использовать Express Tools MPEDIT с параметром допуска (fuzz factor), либо предварительно "сшить" линии вручную.
;; Убедитесь, что все объекты лежат в одной плоскости (имеют одинаковую координату Z), иначе объединение может не сработать.
