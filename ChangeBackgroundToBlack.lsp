(defun c:ChangeBackgroundToBlack ()
  "Изменяет цвет фона в модели на черный"
  ;; Установка цвета фона на черный (RGB: 0, 0, 0)
  (setvar "BACKGROUNDCOLOR" (rgb 0 0 0))
  ;; Обновление экрана для применения изменений
  (princ "\nЦвет фона успешно изменен на черный.")
  (princ)
)

;; Функция для преобразования RGB в значение цвета AutoCAD
(defun rgb (r g b)
  (cond ((and (<= 0 r 255) (<= 0 g 255) (<= 0 b 255))
         (+ (* r 65536) (* g 256) b))
        (t (progn 
             (princ "\nОшибка: Значения RGB должны быть в диапазоне от 0 до 255.")
             nil))))
