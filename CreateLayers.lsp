(defun c:CreateLayers (/ linetypeName linetypeFile)
;; Проверяем, загружен ли тип линии "GOST2.303 5"
  (setq linetypeName "GOST2.303 5")
  (if (not (tblsearch "LTYPE" linetypeName)) ; Если тип линии не найден
    (progn
      (setq linetypeFile (findfile "GOST2.303.lin")) ; Ищем файл GOST2.303.lin
      (if linetypeFile
        (progn
          (command "_.LINETYPE" "_LOAD" linetypeName linetypeFile "") ; Загружаем тип линии
          (princ (strcat "\nТип линии '" linetypeName "' загружен из файла GOST2.303.lin."))
        )
        (princ "\nФайл GOST2.303.lin не найден. Убедитесь, что файл доступен.")
      )
    )
  )
  
  
  
    ;; Проверяем, загружен ли тип линии ACAD_ISO04W100
  (setq linetypeName "ACAD_ISO04W100")
  (if (not (tblsearch "LTYPE" linetypeName)) ; Если тип линии не найден
    (progn
      (setq linetypeFile (findfile "acad.lin")) ; Ищем файл acad.lin
      (if linetypeFile
        (progn
          (command "_.LINETYPE" "_LOAD" linetypeName linetypeFile "") ; Загружаем тип линии
          (princ (strcat "\nТип линии '" linetypeName "' загружен из файла acad.lin."))
        )
        (princ "\nФайл acad.lin не найден. Убедитесь, что стандартная библиотека AutoCAD доступна.")
      )
    )
  )
  
  
  
  
  
  
  
  

;; Создаём слой "Оси"
  (if (not (tblsearch "LAYER" "Оси")) ; Проверяем, существует ли слой "Оси"
    (progn
      (command "_.LAYER" "_M" "Оси" "_C" "187" "Оси" "_L" "ГОСТ 2.303 5" "Оси" "_LW" "0.09" "Оси" "") ; Создаём слой и задаём свойства
      (princ "\nСлой 'Оси' создан: цвет = 187, тип линии = ГОСТ 2.303 5, вес линии = 0.09.")
    )
    (princ "\nСлой 'Оси' уже существует.")
  )

;; Создаём слой "Основная"
  (if (not (tblsearch "LAYER" "Основная")) ; Проверяем, существует ли слой "Основная"
    (progn
      (command "_.LAYER" "_M" "Основная" "_C" "150" "Основная" "_LW" "0.3" "Основная" "") ; Создаём слой и задаём свойства
      (princ "\nСлой 'Основная' создан: цвет = 150, вес линии = 0.3.")
    )
    (princ "\nСлой 'Основная' уже существует.")
  )
  
;; Создаём слой "Основная 2"
  (if (not (tblsearch "LAYER" "Основная 2")) ; Проверяем, существует ли слой "Основная 2"
    (progn
      (command "_.LAYER" "_M" "Основная 2" "_C" "11" "Основная 2" "_LW" "0.3" "Основная 2" "") ; Создаём слой и задаём свойства
      (princ "\nСлой 'Основная 2' создан: цвет = 11, вес линии = 0.3.")
    )
    (princ "\nСлой 'Основная 2' уже существует.")
  )
  
;; Создаём слой "Оформление"
  (if (not (tblsearch "LAYER" "Оформление")) ; Проверяем, существует ли слой "Оформление"
    (progn
      (command "_.LAYER" "_M" "Оформление" "_C" "241" "Оформление" "_LW" "0.13" "Оформление" "") ; Создаём слой и задаём свойства
      (princ "\nСлой 'Оформление' создан: цвет = 241, вес линии = 0.13.")
    )
    (princ "\nСлой 'Оформление' уже существует.")
  )
  
   
;; Создаём слой "Размеры"
  (if (not (tblsearch "LAYER" "Размеры")) ; Проверяем, существует ли слой "Размеры"
    (progn
      (command "_.LAYER" "_M" "Размеры" "_C" "40" "Размеры" "_LW" "0.13" "Размеры" "") ; Создаём слой и задаём свойства
      (princ "\nСлой 'м' создан: цвет = 40, вес линии = 0.13.")
    )
    (princ "\nСлой 'Размеры' уже существует.")
  )
  
;; Создаём слой "Пунктир"
  (if (not (tblsearch "LAYER" "Пунктир")) ; Проверяем, существует ли слой "Пунктир"
    (progn
      (command "_.LAYER" "_M" "Пунктир" "_C" "81" "Пунктир" "_L" "ГОСТ 2.303 4" "Пунктир" "_LW" "0.09" "Пунктир" "") ; Создаём слой и задаём свойства
      (princ "\nСлой 'Пунктир' создан: цвет = 81, тип линии = ГОСТ 2.303 4, вес линии = 0.09.")
    )
    (princ "\nСлой 'Пунктир' уже существует.")
  )
  
;; Создаём слой "Текст"
  (if (not (tblsearch "LAYER" "Текст")) ; Проверяем, существует ли слой "Текст"
    (progn
      (command "_.LAYER" "_M" "Текст" "_C" "140" "Текст" "_LW" "0.15" "Текст" "") ; Создаём слой и задаём свойства
      (princ "\nСлой 'Текст' создан: цвет = 140, вес линии = 0.15.")
    )
    (princ "\nСлой 'Текст' уже существует.")
  )
  
;; Создаём слой "Тонкая"
  (if (not (tblsearch "LAYER" "Тонкая")) ; Проверяем, существует ли слой "Тонкая"
    (progn
      (command "_.LAYER" "_M" "Тонкая" "_C" "140" "Тонкая" "_LW" "0.09" "Тонкая" "") ; Создаём слой и задаём свойства
      (princ "\nСлой 'Тонкая' создан: цвет = 140, вес линии = 0.09.")
    )
    (princ "\nСлой 'Тонкая' уже существует.")
  ) 
  
;; Создаём слой "Швы"
  (if (not (tblsearch "LAYER" "Швы")) ; Проверяем, существует ли слой "Швы"
    (progn
      (command "_.LAYER" "_M" "Швы" "_C" "97" "Швы" "_LW" "0.13" "Швы" "") ; Создаём слой и задаём свойства
      (princ "\nСлой 'Швы' создан: цвет = 97, вес линии = 0.13.")
    )
    (princ "\nСлой 'Швы' уже существует.")
  ) 
  
;; Создаём слой "Штриховка"
  (if (not (tblsearch "LAYER" "Штриховка")) ; Проверяем, существует ли слой "Штриховка"
    (progn
      (command "_.LAYER" "_M" "Штриховка" "_C" "17" "Штриховка" "_LW" "0.09" "Штриховка" "") ; Создаём слой и задаём свойства
      (princ "\nСлой 'Штриховка' создан: цвет = 17, вес линии = 0.09.")
    )
    (princ "\nСлой 'Штриховка' уже существует.")
  ) 

;; Создаём слой "Вспомогательные"
  (if (not (tblsearch "LAYER" "Вспомогательные")) ; Проверяем, существует ли слой "Вспомогательные"
    (progn
      (command "_.LAYER" "_M" "Вспомогательные" "_C" "30" "Вспомогательные" "_LW" "0.15" "Вспомогательные" "") ; Создаём слой и задаём свойства
      (princ "\nСлой 'Вспомогательные' создан: цвет = 30, вес линии = 0.15.")
    )
    (princ "\nСлой 'Вспомогательные' уже существует.")
  ) 
  
;; Создаём слой "Defpoints"
  (if (not (tblsearch "LAYER" "Defpoints")) ; Проверяем, существует ли слой "Defpoints"
    (progn
      (command "_.LAYER" "_M" "Defpoints" "_C" "251" "Defpoints" "_LW" "0.15" "Defpoints" "") ; Создаём слой и задаём свойства
      (princ "\nСлой 'Defpoints' создан: цвет = 251, вес линии = 0.15.")
    )
    (princ "\nСлой 'Defpoints' уже существует.")
  ) 

;; Создаём слой "0"
  (if (not (tblsearch "LAYER" "0")) ; Проверяем, существует ли слой "0"
    (progn
      (command "_.LAYER" "_M" "0" "_C" "белый" "0" "_LW" "0.15" "0" "") ; Создаём слой и задаём свойства
      (princ "\nСлой '0' создан: цвет = белый, вес линии = 0.15.")
    )
    (princ "\nСлой '0' уже существует.")
  ) 


;; Изменяем свойства слоя "Существующий"
  (if (tblsearch "LAYER" "Существующий") ; Проверяем, существует ли слой "Существующий"
    (progn
      (setq layerDef (tblobjname "LAYER" "Существующий")) ; Получаем объект слоя
      ;; Меняем цвет на 123
      (entmod (subst '(62 . 123) (assoc 62 (entget layerDef)) (entget layerDef)))
      ;; Меняем тип линии на ACAD_ISO04W100
      (entmod (subst '(6 . "ACAD_ISO04W100") (assoc 6 (entget layerDef)) (entget layerDef)))
      ;; Устанавливаем слой как "не печатаемый" (флаг 290: 0 = не печатаемый, 1 = печатаемый)
      (entmod (subst '(290 . 0) (assoc 290 (entget layerDef)) (entget layerDef)))
	  ;; Устанавливаем вес линии на 0.09
      (entmod (subst '(370 . 9) (assoc 370 (entget layerDef)) (entget layerDef))) ; 9 = 0.09 мм
      (princ "\nСлой 'Существующий' изменён: цвет = 123, тип линии = ACAD_ISO04W100, вес линии = 0.09, слой не печатаемый.")
    )
    (princ "\nСлой 'Существующий' не найден.")
  )
  
;; Изменяем свойства слоя "Пунктир"
  (if (tblsearch "LAYER" "Пунктир") ; Проверяем, существует ли слой "Пунктир"
    (progn
      (setq layerDef (tblobjname "LAYER" "Пунктир")) ; Получаем объект слоя
      ;; Меняем цвет на 123
      (entmod (subst '(62 . 125) (assoc 62 (entget layerDef)) (entget layerDef)))
      ;; Меняем тип линии на ГОСТ 2.303 4
      (entmod (subst '(6 . "ГОСТ 2.303 4") (assoc 6 (entget layerDef)) (entget layerDef)))
      ;; Устанавливаем слой как "не печатаемый" (флаг 290: 0 = не печатаемый, 1 = печатаемый)
      (entmod (subst '(290 . 1) (assoc 290 (entget layerDef)) (entget layerDef)))
	  ;; Устанавливаем вес линии на 0.09
      (entmod (subst '(370 . 9) (assoc 370 (entget layerDef)) (entget layerDef))) ; 9 = 0.09 мм
      (princ "\nСлой 'Пунктир' изменён: цвет = 123, тип линии = ГОСТ 2.303 4, вес линии = 0.09, слой не печатаемый.")
    )
    (princ "\nСлой 'Пунктир' не найден.")
	(progn
      (command "_.LAYER" "_M" "Пунктир" "_C" "81" "Пунктир" "_L" "ГОСТ 2.303 4" "Пунктир" "_LW" "0.09" "Пунктир" "") ; Создаём слой и задаём свойства
      (princ "\nСлой 'Пунктир' создан: цвет = 81, тип линии = ГОСТ 2.303 4, вес линии = 0.09.")
    )
  )
  
  
  
  (command "_.REGEN") ; Регенерация чертежа

  (princ)
)
