(defun c:CreateDimension (/ pt1 pt2 dimObj)
  (setq pt1 (getpoint "\nВыберите первую точку для размера: "))
  (setq pt2 (getpoint pt1 "\nВыберите вторую точку для размера: "))
  
  ;; Проверка, что точки не совпадают
  (if (not (equal pt1 pt2 1e-6))
    (progn
      ;; Создание линейного размера
      (setq dimObj (entmake
                     (list
                       '(0 . "DIMENSION")       ; Тип объекта - размер
                       '(100 . "AcDbEntity")    ; Стандартные свойства объекта
                       '(100 . "AcDbDimension")
                       (cons 10 pt1)            ; Начальная точка размерной линии
                       (cons 13 pt2)            ; Конечная точка размерной линии
                       (cons 11 (mapcar '+ pt1 (polar pt1 (/ pi 2) 1.0))) ; Метка размера
                       '(70 . 0)                ; Тип размера (0 - горизонтальный или вертикальный)
                       '(50 . 0.0)              ; Угол поворота текста размера
                       '(1 . "")                ; Текст размера (пустой строкой будет автоматический расчет)
                     )
                   )
      )
      (if dimObj
        (princ "\nРазмер создан успешно.")
        (princ "\nНе удалось создать размер.")
      )
    )
    (princ "\nТочки совпадают, размер не может быть создан.")
  )
  
  (princ)  ; Возврат управления без вывода дополнительных сообщений
)

(princ "\nВведите 'CreateDimension' для создания размера по двум точкам.")
