;; ^C^C(if (not c:GreenColorElemets)(load "GreenColorElemets.lsp"));GreenColorElemets
;; изменяет цвет выбранных объектов на зеленый.
;; Вариант 1: Самый простой (с ручным выбором)
;; Этот код запускает команду CHPROP (Change Properties) с предустановленным цветом 3 (зеленый). Это самый надежный способ, так как использует встроенную команду AutoCAD.


(defun C:GreenColorElemets ( / ss)
  ;; Команда для быстрой смены цвета на зеленый
  (princ "\nВыберите объекты для изменения цвета на ЗЕЛЕНЫЙ: ")
  ;; Запрашиваем выбор объектов
  (setq ss (ssget))
  ;; Если объекты выбраны
  (if ss
    (progn
      ;; Запускаем стандартную команду изменения свойств
      (command "_.CHPROP" ss "" "_Color" 3 "")
      (princ (strcat "\nГотово. Цвет изменен на Зеленый (индекс 3) для " (itoa (sslength ss)) " объектов."))
    )
    (princ "\nНе выбрано ни одного объекта.")
  )
  (princ)
)
